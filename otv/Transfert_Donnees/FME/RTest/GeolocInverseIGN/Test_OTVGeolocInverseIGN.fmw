FME workspace Test_OTVGeolocInverseIGN.fmw

Parameters:
- SourceDataset_GEOJSON = $(FME_MF_DIR)sourceTest.json   # URL ou fichier GeoJSON source 
- Test_ReverseGeocodePreference = StreetAddress
- Test_maximumResponses = 2   # Nombre de réponses maximales
- Test_distMaxi = 100   # Distance maximale de recherche
- DestDataset_POSTGRES = OTV_postgres   # Connexion 

Readers:
- GEOJSON_2: GEOJSON from $(SourceDataset_GEOJSON)

Writers:
- POSTGRES_1: POSTGRES to $(DestDataset_POSTGRES)

sourceTestgolocInverse (reader GEOJSON_2)
    attributes: id int
    -> OTV_GeolocInverseIGN [DonneesGeolocalisees]
OTV_GeolocInverseIGN
    ReverseGeocodePreference = $(Test_ReverseGeocodePreference)
    distMaxi = $(Test_distMaxi)
    maximumResponses = $(Test_maximumResponses)
    StreetAddress -> AttributeRenamer
    CadastralParcel -> AttributeRenamer
    Administratif -> AttributeRenamer
    PointOfInterest -> AttributeRenamer
    PasDeGeomSource -> AttributeRenamer
AttributeRenamer
    ATTR_TABLE = RENAME_SET_DEFAULT id > id_objet_test
    MISSING_INPUT_ATTRS = REMOVE
    -> geoloc_inverse_ign (writer POSTGRES_1)
geoloc_inverse_ign (writer POSTGRES_1)
    attributes: id_objet_test int4, GeolocInverse.Numero varchar(80), GeolocInverse.Rue varchar(80), GeolocInverse.Commune varchar(80), GeolocInverse.Departement varchar(80), GeolocInverse.CodeCommuneInsee varchar(80), GeolocInverse.CodePostal varchar(80), GeolocInverse.DistanceObjet float4, GeolocInverse.x_wgs84 float4, GeolocInverse.y_wgs84 float4, GeolocInverse.ParcelleComplete varchar(80), GeolocInverse.Feuille varchar(80), GeolocInverse.Section varchar(80), GeolocInverse.CommuneAbsorbee varchar(80), GeolocInverse.Arrondissement varchar(80), GeolocInverse.Type varchar(80), GeolocInverse.typeGeoloc text, GeolocInverse.Nom varchar(80), GeolocInverse.Nature varchar(80)
